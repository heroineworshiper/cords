# template for cord lock sizes

# the hole radiuses
R = [
    1.0,
    1.25,
    1.5,
    1.75,
    2.0,
    2.25,
    2.5,
    2.75,
    3.0,
    3.25,
    3.5,
    3.75,
    4.0
]

# the opening size
#OPENING = 1.0
OPENING = 2.0
# the overlap between the opening & hole
OVERLAP = .5

# the opening depth
OPENING_D = 3.0

# the opening width
OPENING_W = 5.0

# outer radius of the tool
OUTER_R = 20.0

# space between each hole for the straight tool
W = 8

import FreeCAD as App
import FreeCADGui as Gui
import Sketcher
import Part
import math


# number of holes
N = len(R)

doc = App.activeDocument()
gui = Gui.activeDocument()

class Turtle:
    def __init__(self, x, y, angle):
        self.x = x
        self.y = y
        self.angle = angle

    def move(self, distance):
        self.x += distance * math.cos(self.angle)
        self.y += distance * math.sin(self.angle)

    def draw(self, sketch, distance):
        x2 = self.x + distance * math.cos(self.angle)
        y2 = self.y + distance * math.sin(self.angle)
        sketch.addGeometry(Part.LineSegment(App.Vector(self.x, self.y, 0.0),
                App.Vector(x2, y2, 0.0)),
            False)
        self.x = x2
        self.y = y2

    def rotate(self, diff):
        self.angle -= diff

def extrudeIt(fwd, rev, src):
    result = doc.addObject('Part::Extrusion', 'holes')
    result.DirMode = "Normal"
    result.DirLink = None
    result.LengthFwd = fwd
    result.LengthRev = rev
    result.Solid = True
    result.Reversed = False
    result.Symmetric = False
    result.TaperAngle = 0.000000000000000
    result.TaperAngleRev = 0.000000000000000
    result.Base = src

def toRad(angle):
    return angle * math.pi * 2.0 / 360.0

def draw_opening(sketch, r1, hole_r, x, y, angle):
    coords = [
        x - OPENING / 2, y + hole_r - OVERLAP,
        x + OPENING / 2, y + hole_r - OVERLAP,
        x + OPENING / 2, y + hole_r + 1.0,
        x + OPENING_W / 2, y + hole_r + 1.0 + OPENING_D,
        x + OPENING_W / 2, y + hole_r + 2.0 + OPENING_D,
        x - OPENING_W / 2, y + hole_r + 2.0 + OPENING_D,
        x - OPENING_W / 2, y + hole_r + 1.0 + OPENING_D,
        x - OPENING / 2, y + hole_r + 1.0,
        x - OPENING / 2, y + hole_r - OVERLAP,
    ]
    for i in range(0, len(coords) - 2, 2):
        sketch.addGeometry(Part.LineSegment(
            App.Vector(coords[i], coords[i + 1], 0.0),
            App.Vector(coords[i + 2], coords[i + 3], 0.0)),
        False)

#    distance2 = math.hypot(OPENING_D, (OPENING_W - OPENING) / 2.0)
#    angle2 = math.atan2((OPENING_W - OPENING) / 2.0, OPENING_D)
#    turtle = Turtle(x, y, angle)
#    turtle.rotate(toRad(90.0))
#    turtle.move(-OPENING / 2)
#    turtle.draw(sketch, OPENING)
#    turtle.rotate(-toRad(90.0))
#    turtle.draw(sketch, hole_r + 1.0)
#    turtle.rotate(angle2)
#    turtle.draw(sketch, distance2)
#    turtle.rotate(-angle2)
#    turtle.draw(sketch, 1.0)
#    turtle.rotate(-toRad(90))
#    turtle.draw(sketch, OPENING_W)
#    turtle.rotate(-toRad(90))
#    turtle.draw(sketch, 1.0)
#    turtle.rotate(-angle2)
#    turtle.draw(sketch, distance2)
#    turtle.rotate(angle2)
#    turtle.draw(sketch, hole_r + 1.0)

def draw_triangle(sketch, x, y, r):
    coords = [
        x - r, y + r,
        x + r, y + r,
        x, y - r,
        x - r, y + r
    ]
    for i in range(0, len(coords) - 2, 2):
        sketch.addGeometry(Part.LineSegment(
            App.Vector(coords[i], coords[i + 1], 0.0),
            App.Vector(coords[i + 2], coords[i + 3], 0.0)),
        False)


hole_sketch = doc.addObject('Sketcher::SketchObject','holes')
opening_sketch = doc.addObject('Sketcher::SketchObject','openings')
# maximum width of the previous hole & opening
prev_w = 0
x = .5
for i in range(N):
    hole_r = R[i]
# circular tool.  More expensive
# distance from center of the current hole to the center of the tool
#    r1 = OUTER_R - OPENING_D - 1 - hole_r
# angle of the current hole
#    angle = i * 2 * math.pi / N
#    x = math.cos(angle) * r1
#    y = math.sin(angle) * r1
# straight tool
    r1 = OUTER_R - OPENING_D - 1 - hole_r
    angle = toRad(90.0)

# maximum width of the opening & hole
# holes must have 3mm gaps.  openings must have 1mm gaps
    w2 = max([OPENING_W / 2 + 0.5, hole_r + 1.5])
    x += w2 + prev_w
    prev_w = w2
    y = r1
#    hole_sketch.addGeometry(Part.Circle(App.Vector(x,y,0),App.Vector(0,0,1),hole_r))
    draw_triangle(hole_sketch, x, y, hole_r)
    draw_opening(opening_sketch, r1, hole_r, x, y, angle)


extrudeIt(3, 1, hole_sketch)
extrudeIt(3, 1, opening_sketch)
